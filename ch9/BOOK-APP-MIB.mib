BOOK-APP-MIB DEFINITIONS ::= BEGIN

IMPORTS
OBJECT-GROUP, NOTIFICATION-GROUP			
FROM SNMPv2-CONF			
enterprises, Integer32, OBJECT-TYPE, MODULE-IDENTITY, OBJECT-IDENTITY, Unsigned32,
NOTIFICATION-TYPE			
FROM SNMPv2-SMI			
TEXTUAL-CONVENTION,DisplayString			
FROM SNMPv2-TC;

bookAppMib MODULE-IDENTITY
    LAST-UPDATED "201409121341Z" 
    ORGANIZATION "org"
    CONTACT-INFO  "xtdwxk@gmail.com"
    DESCRIPTION
    "demo for my book(In-depth understanding of Net-SNMP)"
	REVISION "201409121341Z"
    DESCRIPTION "demo"
::= { netSnmpPlaypen 1 }


netSnmp    OBJECT IDENTIFIER ::= { enterprises 8072}
netSnmpExperimental         OBJECT IDENTIFIER  ::= { netSnmp 9999 }
netSnmpPlaypen              OBJECT IDENTIFIER ::= { netSnmpExperimental 9999 }

--
-- Textual conventions
--
Float1TypeTC ::= TEXTUAL-CONVENTION
DISPLAY-HINT 
"d-1"
STATUS current
DESCRIPTION 
"Description."
SYNTAX Integer32

--
-- Node definitions
--

realTimeData OBJECT-GROUP
    OBJECTS {  realTimeDataX1, realTimeDataY2,realTimeDataZ }
    STATUS current
    DESCRIPTION
    "Real data group."
    ::= { bookAppMib 1 }


parameter OBJECT-GROUP
    OBJECTS {  parameterA, parameterB, parameterC1}
    STATUS current
    DESCRIPTION
    "Parameter data group."
    ::= { bookAppMib 2 }


notificationObjs OBJECT IDENTIFIER::= { bookAppMib 11 }

notificationGroup NOTIFICATION-GROUP
    NOTIFICATIONS { sysAlarmNotify ,alarm1,alarm2 }
    STATUS current
    DESCRIPTION 
    "Notification group."
    ::= { bookAppMib 3 }

realTimeDataTable OBJECT-TYPE
    SYNTAX SEQUENCE OF RealTimeDataEntry
    MAX-ACCESS not-accessible
    STATUS current
    DESCRIPTION
            "Description."
    ::= { realTimeData 1 }

realTimeDataEntry OBJECT-TYPE
    SYNTAX RealTimeDataEntry
    MAX-ACCESS not-accessible
    STATUS current
    DESCRIPTION
            "Description."
    INDEX { realTimeDataIndex }
    ::= { realTimeDataTable 1 }

RealTimeDataEntry ::=
    SEQUENCE { 
            realTimeDataIndex
                    Integer32,
            realTimeDataX1
                    Integer32,
            realTimeDataY2
                    Integer32
        }

realTimeDataIndex OBJECT-TYPE
    SYNTAX Integer32 (1..65536)
    MAX-ACCESS not-accessible
    STATUS current
    DESCRIPTION
            "Index."
    ::= { realTimeDataEntry 1 }

realTimeDataX1 OBJECT-TYPE
    SYNTAX Integer32 (1..65536)
    MAX-ACCESS read-only
    STATUS current
    DESCRIPTION
            "realTimeDataX1."
    ::= { realTimeDataEntry 2 }
	
realTimeDataY2 OBJECT-TYPE
    SYNTAX Integer32 (1..65536)
    MAX-ACCESS read-only
    STATUS current
    DESCRIPTION
            "realTimeDataY2."
    ::= { realTimeDataEntry 3 }

realTimeDataZ OBJECT-TYPE
    SYNTAX Float1TypeTC
    MAX-ACCESS read-only
    STATUS current
    DESCRIPTION
    "realTimeDataZ."
::= { realTimeData 2 }


parameterA OBJECT-TYPE
    SYNTAX Integer32
    MAX-ACCESS read-write
    STATUS current
    DESCRIPTION
            "parameterA."
    ::= { parameter 1 }
	
parameterB OBJECT-TYPE
    SYNTAX DisplayString
    MAX-ACCESS read-write
    STATUS current
    DESCRIPTION
            "parameterB:max lenght is 32 char!"
    ::= { parameter 2 }	

parameterTable OBJECT-TYPE
    SYNTAX SEQUENCE OF ParameterEntry
    MAX-ACCESS not-accessible
    STATUS current
    DESCRIPTION
            "Description."
    ::= { parameter 3 }

parameterEntry OBJECT-TYPE
    SYNTAX ParameterEntry
    MAX-ACCESS not-accessible
    STATUS current
    DESCRIPTION
            "Description."
    INDEX { parameterIndex }
    ::= { parameterTable 1 }

ParameterEntry ::=
    SEQUENCE { 
            parameterIndex
                    Integer32,
            parameterC1
                    Integer32
        }

parameterIndex OBJECT-TYPE
    SYNTAX Integer32 (1..65536)
    MAX-ACCESS not-accessible
    STATUS current
    DESCRIPTION
            "Index."
    ::= { parameterEntry 1 }

parameterC1 OBJECT-TYPE
    SYNTAX Integer32 (1..65536)
    MAX-ACCESS read-write
    STATUS current
    DESCRIPTION
            "parameterC1."
    ::= { parameterEntry 2 }

sysAlarms OBJECT-IDENTITY
    STATUS current
    DESCRIPTION 
            "notification node for system alarms."
    ::= { notificationGroup 0 }		

sysAlarmNotify NOTIFICATION-TYPE
OBJECTS     { alarmCounter,alarm1,alarm2}
    STATUS current
    DESCRIPTION 
            "System Alarm Notify."
    ::= { sysAlarms 1 }

alarm1 OBJECT-TYPE
    SYNTAX Integer32
    MAX-ACCESS accessible-for-notify
    STATUS current
    DESCRIPTION
            "for notification."
    ::= { notificationObjs 1 }

alarm2 OBJECT-TYPE
    SYNTAX DisplayString
    MAX-ACCESS accessible-for-notify
    STATUS current
    DESCRIPTION
            "for notification."
    ::= { notificationObjs 2 }
	
alarmCounter OBJECT-TYPE
    SYNTAX Integer32
    MAX-ACCESS read-write
    STATUS current
    DESCRIPTION
            "for notification count."
    ::= { notificationObjs 3 }	


END
