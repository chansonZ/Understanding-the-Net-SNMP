--
-- BOOK-EXAMPLE-MIB.my
-- MIB generated by MG-SOFT Visual MIB Builder Version 6.0  Build 88
-- Monday, April 12, 2014 at 18:53:08
--

	BOOK-EXAMPLE-MIB DEFINITIONS ::= BEGIN
 
		IMPORTS
			OBJECT-GROUP, NOTIFICATION-GROUP			
				FROM SNMPv2-CONF			
			enterprises, Integer32, OBJECT-TYPE, MODULE-IDENTITY, OBJECT-IDENTITY, Unsigned32,
			NOTIFICATION-TYPE			
				FROM SNMPv2-SMI			
			TEXTUAL-CONVENTION,DisplayString			
				FROM SNMPv2-TC;
	
	
		-- 1.3.6.1.4.1.9999
		bookexampleMib MODULE-IDENTITY 
			LAST-UPDATED "201404121341Z"		-- April 12, 2014 at 13:41 GMT
			ORGANIZATION 
				"BookForExample."
			CONTACT-INFO 
				"Contact-info."
			DESCRIPTION 
				"Description."
			::= { enterprises 9999 }

		
	
--
-- Type definitions
--
	
		ByteINT ::= INTEGER (0..255)

	
--
-- Textual conventions
--
	
		Float1TypeTC ::= TEXTUAL-CONVENTION
			DISPLAY-HINT 
				"d-1"
			STATUS current
			DESCRIPTION 
				"Description."
			SYNTAX Integer32

	
--
-- Node definitions
--
	
		-- 1.3.6.1.4.1.9999.1
		exampleNotifications OBJECT-IDENTITY
			STATUS current
			DESCRIPTION 
				"notification tree."
			::= { bookexampleMib 1 }
			
		-- 1.3.6.1.4.1.9999.1.0
		exampleNotification OBJECT-IDENTITY
			STATUS current
			DESCRIPTION 
				"notification node."
			::= { exampleNotifications 0 }			

		
		-- 1.3.6.1.4.1.9999.1.0.1
		exampleNotify1 NOTIFICATION-TYPE
		    OBJECTS     { exampleNotifyObj1 }
			STATUS current
			DESCRIPTION 
				"Description."
			::= { exampleNotification 1 }

		
		-- 1.3.6.1.4.1.9999.3
		exampleObject OBJECT-IDENTITY
			STATUS current
			DESCRIPTION 
				"Description."
			::= { bookexampleMib 3 }

		
		-- 1.3.6.1.4.1.9999.3.1
		exampleObject1 OBJECT-TYPE
			SYNTAX Integer32
			MAX-ACCESS read-only
			STATUS current
			DESCRIPTION
				"Example:Integer32."
			::= { exampleObject 1 }

		
		-- 1.3.6.1.4.1.9999.3.2
		exampleObject2 OBJECT-TYPE
			SYNTAX ByteINT
			MAX-ACCESS read-write
			STATUS current
			DESCRIPTION
				"Example:ByteINT."
			::= { exampleObject 2 }

		
		-- 1.3.6.1.4.1.9999.3.3
		exampleObject3 OBJECT-TYPE
			SYNTAX Float1TypeTC
			MAX-ACCESS read-write
			STATUS current
			DESCRIPTION
				"Example:Float1TypeTC."
			::= { exampleObject 3 }

		-- 1.3.6.1.4.1.9999.3.4
		exampleObject4 OBJECT-TYPE
			SYNTAX DisplayString
			MAX-ACCESS read-write
			STATUS current
			DESCRIPTION
				"Example:DisplayString."
			::= { exampleObject 4 }
		
		-- 1.3.6.1.4.1.9999.3.9
		simpleTable OBJECT-TYPE
			SYNTAX SEQUENCE OF SimpleEntry
			MAX-ACCESS not-accessible
			STATUS current
			DESCRIPTION
				"Description."
			::= { exampleObject 9 }

		
		-- 1.3.6.1.4.1.9999.3.9.1
		simpleEntry OBJECT-TYPE
			SYNTAX SimpleEntry
			MAX-ACCESS not-accessible
			STATUS current
			DESCRIPTION
				"Description."
			INDEX { simpleTbColum1 }
			::= { simpleTable 1 }

		
		SimpleEntry ::=
			SEQUENCE { 
				simpleTbColum1
					Integer32,
				simpleTbColum2
					Integer32
			 }

		-- 1.3.6.1.4.1.9999.3.9.1.1
		simpleTbColum1 OBJECT-TYPE
			SYNTAX Integer32 (1..65536)
			MAX-ACCESS read-only
			STATUS current
			DESCRIPTION
				"Description."
			::= { simpleEntry 1 }

		
		-- 1.3.6.1.4.1.9999.3.9.1.2
		simpleTbColum2 OBJECT-TYPE
			SYNTAX Integer32
			MAX-ACCESS read-write
			STATUS current
			DESCRIPTION
				"Description."
			::= { simpleEntry 2 }

		-- 1.3.6.1.4.1.9999.3.11
		generalTable OBJECT-TYPE
			SYNTAX SEQUENCE OF GeneralEntry
			MAX-ACCESS not-accessible
			STATUS current
			DESCRIPTION
				"Description."
			::= { exampleObject 11 }

		
		-- 1.3.6.1.4.1.9999.3.11.1
		generalEntry OBJECT-TYPE
			SYNTAX GeneralEntry
			MAX-ACCESS not-accessible
			STATUS current
			DESCRIPTION
				"Description."
			INDEX { generalTbColum1,generalTbColum2 }
			::= { generalTable 1 }

		
		GeneralEntry ::=
			SEQUENCE { 
				generalTbColum1
					Unsigned32,
				generalTbColum2
					Unsigned32,
				generalTbColum3
					DisplayString,
				generalTbColum4
					Integer32					
			 }

		-- 1.3.6.1.4.1.9999.3.9.1.1
		generalTbColum1 OBJECT-TYPE
			SYNTAX Unsigned32
			MAX-ACCESS read-only
			STATUS current
			DESCRIPTION
				"Description."
			::= { generalEntry 1 }

		
		-- 1.3.6.1.4.1.9999.3.11.1.2
		generalTbColum2 OBJECT-TYPE
			SYNTAX Unsigned32
			MAX-ACCESS read-only
			STATUS current
			DESCRIPTION
				"Description."
			::= { generalEntry 2 }
			
		-- 1.3.6.1.4.1.9999.3.11.1.3
		generalTbColum3 OBJECT-TYPE
			SYNTAX DisplayString
			MAX-ACCESS read-write
			STATUS current
			DESCRIPTION
				"Description."
			::= { generalEntry 3 }

		-- 1.3.6.1.4.1.9999.3.11.1.4
		generalTbColum4 OBJECT-TYPE
			SYNTAX Integer32
			MAX-ACCESS read-write
			STATUS current
			DESCRIPTION
				"Description."
			::= { generalEntry 4 }			
		
		-- 1.3.6.1.4.1.9999.4
		objectGroup OBJECT-GROUP
			OBJECTS { exampleObject1, exampleObject2, exampleObject3, simpleTbColum1, simpleTbColum2,generalTbColum3,
			generalTbColum4
				 }
			STATUS current
			DESCRIPTION 
				"Description."
			::= { bookexampleMib 4 }

		
		-- 1.3.6.1.4.1.9999.5
		notificationGroup NOTIFICATION-GROUP
			NOTIFICATIONS { exampleNotify1 ,exampleNotifyObj1}
			STATUS current
			DESCRIPTION 
				"Description."
			::= { bookexampleMib 5 }
			
		-- 1.3.6.1.4.1.9999.10
		notificationObjs OBJECT IDENTIFIER
			 ::= { bookexampleMib 10 }
			 
		-- 1.3.6.1.4.1.9999.10.1
		exampleNotifyObj1 OBJECT-TYPE
			SYNTAX Integer32
			MAX-ACCESS accessible-for-notify
			STATUS current
			DESCRIPTION
				"for notification."
			::= { notificationObjs 1 }
			
		-- 1.3.6.1.4.1.9999.10.2
		exampleNotifyObj2 OBJECT-TYPE
			SYNTAX Integer32
			MAX-ACCESS accessible-for-notify
			STATUS current
			DESCRIPTION
				"optional for notification."
			::= { notificationObjs 2 }			
		
	
	END

--
-- BOOK-EXAMPLE-MIB.my
--
